;;; ===========================================================================
;;; LightingAI.lsp  —  AutoCAD for Mac (AutoLISP)
;;;
;;; Commands defined:
;;;   LIGHTINGAI_GRID     → draw ceiling grid automatically (no picking needed)
;;;   LIGHTINGAI_PLACE    → load luminaire commands generated by Python bridge
;;;   LIGHTINGAI_CLEAR    → erase all AI-* layer entities
;;;   LIGHTINGAI_STATUS   → show current state
;;;   LIGHTINGAI_SETUP    → (optional) manually override grid origin
;;;
;;; How to load (one-time setup):
;;;   In AutoCAD command line type:  (load "/path/to/LightingAI.lsp")
;;;   Or drag-drop the file onto the AutoCAD window.
;;;
;;; Workflow:
;;;   1. Open DWG floor plan in AutoCAD
;;;   2. Type LIGHTINGAI_GRID  →  grid appears automatically, no clicks needed
;;;   3. Run Python bridge in Terminal with your DWG file path
;;;   4. Type LIGHTINGAI_PLACE  →  luminaires placed on drawing
;;; ===========================================================================

;; ── Configuration ────────────────────────────────────────────────────────────
;; Files in ~/ai-lighting/ so macOS never cleans them (unlike /tmp)
(setq LAI:HOME             (getenv "HOME"))
(setq LAI:DATA-DIR         (strcat LAI:HOME "/ai-lighting"))
(setq LAI:ORIGIN-FILE      (strcat LAI:DATA-DIR "/lightingai_origin.json"))
(setq LAI:COMMANDS-FILE    (strcat LAI:DATA-DIR "/lightingai_commands.lsp"))
(setq LAI:TYPECONFIG-FILE  (strcat LAI:DATA-DIR "/lightingai_typeconfig.json"))
(setq LAI:GRID-CFG-FILE    (strcat LAI:DATA-DIR "/lightingai_grid_config.json"))
(setq LAI:BRIDGE-SCRIPT
  (strcat (getvar "ROAMABLEROOTPREFIX")
          "/../ai-lighting/autocad-plugin/lisp/lightingai_bridge.py"))



;; Remembers the last DWG path chosen in the panel (persists across panel sessions)
(setq LAI:LAST-DWG "")

;; Layers the plugin owns (used by CLEAR command)
(setq LAI:LAYERS
  (list "AI-LUMINAIRES" "AI-ZONES" "AI-GRID-ORIGIN"
        "AI-DECKENRASTER" "AI-RASTER-ANNO"
        "AI-DIMENSIONS" "AI-LEGEND" "AI-SCHEDULE" "AI-TITLEBLOCK" "AI-ANNOTATIONS"))

;; ── Helpers ───────────────────────────────────────────────────────────────────

(defun lai:println (msg)
  (princ (strcat "\n[LightingAI] " msg "\n")))

(defun lai:ensure-layer (name color / )
  ;; Use -LAYER (command-line version) — never opens a dialog, works in scripts.
  (if (not (tblsearch "LAYER" name))
    (command "_.-LAYER" "_N" name ""))   ; create if missing
  (command "_.-LAYER" "_C" (itoa color) name "")  ; always set colour
  (princ))

(defun lai:ensure-all-layers ()
  (lai:ensure-layer "AI-LUMINAIRES"    6)
  (lai:ensure-layer "AI-ZONES"         3)
  (lai:ensure-layer "AI-GRID-ORIGIN"   2)
  (lai:ensure-layer "AI-DECKENRASTER" 253)  ; Light gray — grid lines
  (lai:ensure-layer "AI-RASTER-ANNO"   2)  ; Yellow — Startmaß annotations
  (lai:ensure-layer "AI-DIMENSIONS"    7)
  (lai:ensure-layer "AI-LEGEND"        7)
  (lai:ensure-layer "AI-SCHEDULE"      7)
  (lai:ensure-layer "AI-TITLEBLOCK"    7)
  (lai:ensure-layer "AI-ANNOTATIONS"   9))

(defun lai:write-origin-file (x y pitch fp-xmin fp-ymin fp-xmax fp-ymax / fp dwg-dir dwg-name dwg-full dwg-bytes)
  ;; Write the grid origin + detected floor plan bounds to origin.json.
  ;; The floor plan bounds (xmin/ymin/xmax/ymax) are the bounding box of the
  ;; largest LWPOLYLINE detected by LIGHTINGAI_GRID — always the actual store
  ;; footprint regardless of what else is in the DWG (title blocks, etc.).
  ;; The bridge uses these bounds to position the legend correctly.
  ;; DWG path is stored as Latin-1 byte values so non-ASCII chars survive.
  (setq dwg-dir  (getvar "DWGPREFIX"))
  (setq dwg-name (getvar "DWGNAME"))
  (setq dwg-full (if (and dwg-dir (/= dwg-dir ""))
                   (strcat dwg-dir dwg-name)
                   dwg-name))
  (setq dwg-bytes (lai:path-bytes dwg-full))
  (setq fp (open LAI:ORIGIN-FILE "w"))
  (write-line
    (strcat "{\"x\": "         (rtos x 2 4)
            ", \"y\": "        (rtos y 2 4)
            ", \"pitch\": "    (itoa pitch)
            ", \"fp_xmin\": "  (rtos fp-xmin 2 4)
            ", \"fp_ymin\": "  (rtos fp-ymin 2 4)
            ", \"fp_xmax\": "  (rtos fp-xmax 2 4)
            ", \"fp_ymax\": "  (rtos fp-ymax 2 4)
            ", \"dwg_bytes\": [" dwg-bytes "]}")
    fp)
  (close fp)
  (setq fp (open "/tmp/lai_dwg_bytes.txt" "w"))
  (write-line dwg-bytes fp)
  (close fp))

(defun lai:file-exists (path)
  (findfile path))

(defun lai:erase-layer-entities (layername / ss)
  ;; Select all entities on the given layer and erase them
  (setq ss (ssget "_X" (list (cons 8 layername))))
  (if ss (command "_.ERASE" ss ""))
  (princ))

;; ── Helper: read origin JSON and return (list x y pitch) ────────────────────
(defun lai:read-origin ( / fp line x y p tok)
  ;; Returns (list x y pitch) if origin file exists, else nil.
  ;; JSON format: {"x": 1234.0, "y": 5678.0, "pitch": 1250}
  (if (not (lai:file-exists LAI:ORIGIN-FILE))
    nil
    (progn
      (setq fp   (open LAI:ORIGIN-FILE "r"))
      (setq line (read-line fp))
      (close fp)
      ;; Simple extraction: find values after "x":, "y":, "pitch":
      (setq x (atof (cadr (quote-split line "\"x\":"))))
      (setq y (atof (cadr (quote-split line "\"y\":"))))
      (setq p (atof (cadr (quote-split line "\"pitch\":"))))
      (if (and (/= x 0.0) (/= y 0.0) (/= p 0.0))
        (list x y (fix p))
        nil))))

;; ── Helper: read grid lineweight and color from lightingai_grid_config.json ──
;; Format: {"lineweight": 25, "color": 253}
(defun lai:read-grid-lw ( / fp line lw)
  (if (not (lai:file-exists LAI:GRID-CFG-FILE)) nil
    (progn
      (setq fp (open LAI:GRID-CFG-FILE "r"))
      (setq line (read-line fp))
      (close fp)
      (setq lw (atoi (cadr (quote-split line "\"lineweight\":"))))
      (if (and (numberp lw) (>= lw 5) (<= lw 211)) lw nil))))

(defun lai:read-grid-color ( / fp line c)
  (if (not (lai:file-exists LAI:GRID-CFG-FILE)) nil
    (progn
      (setq fp (open LAI:GRID-CFG-FILE "r"))
      (setq line (read-line fp))
      (close fp)
      (setq c (atoi (cadr (quote-split line "\"color\":"))))
      (if (and (numberp c) (>= c 1) (<= c 256)) c nil))))

;; Helper: split string at a substring (simple one-shot)
(defun quote-split (str sep / pos len)
  (setq len (strlen sep))
  (setq pos (vl-string-search sep str))
  (if pos
    (list (substr str 1 pos)
          (substr str (+ pos len 1)))
    (list str "")))

;; ── LIGHTINGAI_GRID ───────────────────────────────────────────────────────────
;;
;; Draws the Rossmann Deckenrasterplan ceiling grid AUTOMATICALLY.
;; Just type LIGHTINGAI_GRID — no clicking, no picking required.
;;
;; Based on professional MAX FRANKE.led plans:
;;   Eisleben 602  (22.01.2026): Startmaß 1.00m / 2.00m, pitch 1250mm
;;   Puderbach 4073 (18.02.2026): Startmaß 1.00m / 2.00m, pitch 1250mm
;;
(defun c:LIGHTINGAI_GRID ( /
    old-layer old-osmode old-cmdecho old-pmode
    xmin xmax ymin ymax
    ox oy draw-ox draw-oy pitch START-X START-Y
    gx gy x-count y-count sub-lw
    first-gx first-gy anno-x anno-y
    offset-x offset-y area-m2 ok
    ss cnt i ent ed pair
    vx vy vx-min vx-max vy-min vy-max
    bb-w bb-h bb-area best-area found-poly)

  ;; ── Save AutoCAD state ──────────────────────────────────────────────────
  (setq old-layer   (getvar "CLAYER"))
  (setq old-osmode  (getvar "OSMODE"))
  (setq old-cmdecho (getvar "CMDECHO"))
  (setq old-pmode   (getvar "PDMODE"))
  (setvar "CMDECHO" 0)
  (setvar "OSMODE"  0)

  (lai:println "")
  (lai:println "=== LIGHTINGAI DECKENRASTER — Startmass 1.00m/2.00m, Raster 625mm ===")

  ;; ── Rossmann standard constants ──────────────────────────────────────────
  ;; 625mm = Referenzmaß Rasterdecke (tile module).
  ;; Luminaires are placed every 2 tiles = 1250mm along each shelf run.
  (setq pitch   625.0)
  (setq START-X 1000.0)   ; 1.00m from left wall
  (setq START-Y 2000.0)   ; 2.00m from entry/bottom wall

  ;; ── Read user-chosen line weight + color (set by GUI dialog) ────────────
  (setq lai:grid-lw    (lai:read-grid-lw))
  (setq lai:grid-color (lai:read-grid-color))
  (if (null lai:grid-lw)    (setq lai:grid-lw    25))
  (if (null lai:grid-color) (setq lai:grid-color 253))

  ;; ── Find store boundary from LWPOLYLINE entities ──────────────────────────
  ;; Scan every LWPOLYLINE for its bounding box.
  ;; Accept bounding-box areas 50 m² – 1 800 m² (5e7 – 1.8e9 mm²).
  ;; The LARGEST polygon in that range is the building footprint.
  ;; Upper bound 1.8e9 excludes A0 drawing-sheet borders (~2500 m²)
  ;; while accommodating buildings up to ~1800 m² footprint.
  (setq ss (ssget "_X" (list (cons 0 "LWPOLYLINE"))))
  (setq best-area 0.0)
  (setq found-poly nil)
  (if ss
    (progn
      (setq cnt (sslength ss))
      (setq i 0)
      (while (< i cnt)
        (setq ent (ssname ss i))
        (setq ed  (entget ent))
        (setq vx-min nil)
        (foreach pair ed
          (if (= (car pair) 10)
            (progn
              (setq vx (car  (cdr pair)))
              (setq vy (cadr (cdr pair)))
              (if (null vx-min)
                (progn
                  (setq vx-min vx) (setq vx-max vx)
                  (setq vy-min vy) (setq vy-max vy))
                (progn
                  (if (< vx vx-min) (setq vx-min vx))
                  (if (> vx vx-max) (setq vx-max vx))
                  (if (< vy vy-min) (setq vy-min vy))
                  (if (> vy vy-max) (setq vy-max vy)))))))
        (if vx-min
          (progn
            (setq bb-w    (abs (- vx-max vx-min)))
            (setq bb-h    (abs (- vy-max vy-min)))
            (setq bb-area (* bb-w bb-h))
            ;; Building footprint: 50 m² to 1 800 m² → 5e7 to 1.8e9 mm²
            ;; Pick LARGEST — building footprint > all interior room polygons.
            (if (and (> bb-area 5.0e7) (< bb-area 1.8e9) (> bb-area best-area))
              (progn
                (setq best-area bb-area)
                (setq found-poly T)
                (setq xmin vx-min) (setq xmax vx-max)
                (setq ymin vy-min) (setq ymax vy-max)))))
        (setq i (1+ i)))))

  ;; Fall back to drawing extents only when no suitable LWPOLYLINE exists
  (if (not found-poly)
    (progn
      (lai:println "No store LWPOLYLINE found — using drawing extents (ZOOM E)")
      (command "_.ZOOM" "_E")
      (setq xmin (car  (getvar "EXTMIN")))
      (setq ymin (cadr (getvar "EXTMIN")))
      (setq xmax (car  (getvar "EXTMAX")))
      (setq ymax (cadr (getvar "EXTMAX"))))
    (lai:println (strcat "Store outline: "
                         (rtos (/ (abs (* (- xmax xmin) (- ymax ymin))) 1.0e6) 2 0)
                         " m2 bounding box (from LWPOLYLINE)")))

  (lai:println (strcat "Boundary: (" (rtos xmin 2 1) ", " (rtos ymin 2 1)
                       ") -> (" (rtos xmax 2 1) ", " (rtos ymax 2 1) ")"))

  ;; ── Validate ─────────────────────────────────────────────────────────────
  (setq ok
    (and (< xmin xmax)
         (< ymin ymax)
         (> (abs (- xmax xmin)) 500.0)
         (> (abs (- ymax ymin)) 500.0)
         (< (abs xmin) 1.0e18)
         (< (abs ymin) 1.0e18)))

  (if ok
    (progn
      ;; ── Grid origin ───────────────────────────────────────────────────────
      ;; ox/oy = light annotation origin (used for Startmaß label only).
      ;; draw-ox/draw-oy = 0 so grid lines fall on exact multiples of pitch
      ;; from the absolute coordinate origin.  The Python pipeline snaps
      ;; lights to ox=0 for georeferenced plans (coords > 10 million mm),
      ;; so tile boundaries land at k×625 — perfectly on these grid lines.
      (setq ox     (+ xmin START-X))
      (setq oy     (+ ymin START-Y))
      (setq draw-ox 0.0)
      (setq draw-oy 0.0)
      (lai:println (strcat "Light origin: (" (rtos ox 2 1) ", " (rtos oy 2 1) ")"))
      (lai:println (strcat "Grid tile origin: (" (rtos draw-ox 2 1) ", " (rtos draw-oy 2 1) ")"))

      ;; ── Create layers ─────────────────────────────────────────────────────
      (lai:ensure-layer "AI-DECKENRASTER" 253)
      (lai:ensure-layer "AI-RASTER-ANNO"    2)

      ;; Erase any previous grid on these layers
      (lai:erase-layer-entities "AI-DECKENRASTER")
      (lai:erase-layer-entities "AI-RASTER-ANNO")

      ;; ── Vertical lines (constant X) — drawn at tile boundaries ───────────
      ;; Start from the first k×pitch ≥ xmin (draw-ox=0, absolute-coord grid).
      (setq gx (+ draw-ox (* (fix (/ (- xmin draw-ox) pitch)) pitch)))
      (if (< gx xmin) (setq gx (+ gx pitch)))
      (setq first-gx gx)
      (setq x-count 0)
      (while (<= gx xmax)
        (entmake
          (list (cons 0 "LINE")
                (cons 8 "AI-DECKENRASTER")
                (cons 62 lai:grid-color)
                (cons 370 lai:grid-lw)
                (cons 10 (list gx ymin 0.0))
                (cons 11 (list gx ymax 0.0))))
        (setq gx      (+ gx pitch))
        (setq x-count (1+ x-count)))

      ;; ── Horizontal lines (constant Y) — drawn at tile boundaries ─────────
      (setq gy (+ draw-oy (* (fix (/ (- ymin draw-oy) pitch)) pitch)))
      (if (< gy ymin) (setq gy (+ gy pitch)))
      (setq first-gy gy)
      (setq y-count 0)
      (while (<= gy ymax)
        (entmake
          (list (cons 0 "LINE")
                (cons 8 "AI-DECKENRASTER")
                (cons 62 lai:grid-color)
                (cons 370 lai:grid-lw)
                (cons 10 (list xmin gy 0.0))
                (cons 11 (list xmax gy 0.0))))
        (setq gy      (+ gy pitch))
        (setq y-count (1+ y-count)))

      ;; Quadrant dividers are drawn INSIDE each luminaire tile block itself
      ;; (generated by the Python bridge in generate_block_defs).  No extra
      ;; grid subdivision lines needed here — one 625 mm cell per tile block.

      ;; ── Annotation text (Startmaß label) ─────────────────────────────────
      ;; Show the light-position offset (1.00m / 2.00m), not the tile-edge offset.
      (setq offset-x (- ox xmin))
      (setq offset-y (- oy ymin))
      (setq anno-x   (+ xmin (* pitch 0.5)))
      (setq anno-y   (+ ymax (* pitch 0.3)))
      (entmake
        (list (cons 0 "TEXT")
              (cons 8 "AI-RASTER-ANNO")
              (cons 62 2)
              (cons 10 (list anno-x anno-y 0.0))
              (cons 40 (* pitch 0.14))
              (cons 50 0.0)
              (cons 1 (strcat "Startmass Rasterdecke  "
                              (rtos (/ offset-x 1000.0) 2 2)
                              "m / "
                              (rtos (/ offset-y 1000.0) 2 2)
                              "m   Raster=0.625m"))))

      ;; ── Offset dimension texts ────────────────────────────────────────────
      (if (> offset-x 10.0)
        (entmake
          (list (cons 0 "TEXT")
                (cons 8 "AI-RASTER-ANNO")
                (cons 62 2)
                (cons 10 (list (/ (+ xmin first-gx) 2.0)
                               (- ymin (* pitch 0.2)) 0.0))
                (cons 40 (* pitch 0.12))
                (cons 50 0.0)
                (cons 1 (strcat (rtos (/ offset-x 1000.0) 2 2) "m")))))
      (if (> offset-y 10.0)
        (entmake
          (list (cons 0 "TEXT")
                (cons 8 "AI-RASTER-ANNO")
                (cons 62 2)
                (cons 10 (list (- xmin (* pitch 0.22))
                               (/ (+ ymin first-gy) 2.0) 0.0))
                (cons 40 (* pitch 0.12))
                (cons 50 0.0)
                (cons 1 (strcat (rtos (/ offset-y 1000.0) 2 2) "m")))))

      ;; ── Save origin + auto-launch the AI bridge ──────────────────────────
      ;; Pass the detected floor plan bounds so the bridge can position the
      ;; legend relative to the actual store — not DWG artifacts.
      (lai:write-origin-file ox oy (fix pitch) xmin ymin xmax ymax)
      ;; Kick off the bridge in Terminal now so it processes while the user
      ;; configures symbols.  By Step 3 (Place Lights) it will be done.
      (lai:run-bridge-from-bytes)

      ;; ── Summary ───────────────────────────────────────────────────────────
      (setq area-m2 (/ (abs (* (- xmax xmin) (- ymax ymin))) 1.0e6))
      (lai:println (strcat "Lines: " (itoa x-count) " vertical + "
                                      (itoa y-count) " horizontal ("
                                      (itoa (* x-count y-count)) " intersections)"))
      (lai:println (strcat "Area:  " (rtos area-m2 2 1) " m2"))
      (lai:println "Layer: AI-DECKENRASTER (color 253) + AI-RASTER-ANNO (yellow)")
      (lai:println "AI bridge launched in Terminal — configure symbols while it runs.")
      (lai:println "When Terminal says Done, click Place Lights.")
      (lai:println "Clear: LIGHTINGAI_CLEAR")
    )
    (progn
      ;; Extents were invalid — tell the user what we got so they can diagnose
      (lai:println (strcat "ERROR: Extents invalid — EXTMIN=(" (rtos xmin 2 1)
                           "," (rtos ymin 2 1) ")  EXTMAX=("
                           (rtos xmax 2 1) "," (rtos ymax 2 1) ")"))
      (lai:println "Try: run 'ZOOM A' in AutoCAD, then run LIGHTINGAI_GRID again.")
      (lai:println "Also ensure the DWG floor plan has entities in Model Space.")))

  ;; ── Restore state (always executes, even on error) ───────────────────────
  (setvar "CLAYER"  old-layer)
  (setvar "OSMODE"  old-osmode)
  (setvar "CMDECHO" old-cmdecho)
  (setvar "PDMODE"  old-pmode)
  (princ))

;; ── LIGHTINGAI_SETUP ─────────────────────────────────────────────────────────
;;
;; OPTIONAL — only needed to override the automatic Startmaß.
;; LIGHTINGAI_GRID now calculates the origin automatically from drawing extents.
;; Use SETUP only when the professional plan specifies a different offset.
;;
(defun c:LIGHTINGAI_SETUP ( / pt pitch)
  (lai:println "(Optional) Override Startmaß — snap to a specific grid origin point.")
  (lai:println "NOTE: LIGHTINGAI_GRID works without this. Only use SETUP to override.")
  (lai:println "Tip: turn on OSNAP → Intersection, then click the grid origin.")

  (setq pt (getpoint "\n[LightingAI] Startmaß — pick grid origin: "))
  (if (null pt)
    (progn (lai:println "Cancelled.") (exit)))

  (initget 6)  ; no negative, no zero
  (setq pitch (getint "\n[LightingAI] Grid pitch in mm [press Enter for 625]: "))
  (if (null pitch) (setq pitch 625))

  ;; Create AI-GRID-ORIGIN layer
  (lai:ensure-layer "AI-GRID-ORIGIN" 2)

  ;; Erase any previous marker
  (lai:erase-layer-entities "AI-GRID-ORIGIN")

  ;; Place a POINT entity at the origin (visible as a node)
  (setvar "CLAYER" "AI-GRID-ORIGIN")
  (command "_.POINT" pt)

  ;; Place a small annotation text next to the point
  (command "_.TEXT"
           (list (+ (car pt) (* pitch 0.05))
                 (+ (cadr pt) (* pitch 0.05))
                 0)
           (* pitch 0.08)
           0
           (strcat "Startmaß  pitch=" (itoa pitch)))

  (setvar "CLAYER" "0")

  ;; Manual setup: no auto-detected floor plan bounds; bridge falls back to zone bounds.
  (lai:write-origin-file (car pt) (cadr pt) pitch 0 0 0 0)

  (lai:println (strcat "Grid origin set:  X=" (rtos (car pt) 2 1)
                       "  Y=" (rtos (cadr pt) 2 1)
                       "  pitch=" (itoa pitch) " mm"))
  (lai:println "Next: run the Python bridge in Terminal, then run LIGHTINGAI_PLACE.")
  (princ))

;; ── LIGHTINGAI_PLACE ─────────────────────────────────────────────────────────
;;
;; Loads and executes the luminaire command file that the Python bridge
;; wrote to /tmp/lightingai_commands.lsp.
;;
;; The designer runs the Python bridge in Terminal first (see README_MAC.md),
;; then calls this command to pull the result into the drawing.
;;
(defun c:LIGHTINGAI_PLACE ( / cmdfile)
  (setq cmdfile LAI:COMMANDS-FILE)

  (if (not (lai:file-exists LAI:TYPECONFIG-FILE))
    (progn
      (lai:println "No symbol config found — open the LightingAI panel and configure symbols first.")
      (exit)))

  (if (not (lai:file-exists cmdfile))
    (progn
      (lai:println "No commands file yet — the AI bridge is still running in Terminal.")
      (lai:println "Wait for Terminal to show 'Done', then click Place Lights again.")
      (exit)))

  (lai:println "Placing luminaires…")
  (lai:ensure-all-layers)
  (load cmdfile)
  (lai:println "Done. All luminaires placed.")
  (lai:println "Run LIGHTINGAI_CLEAR to remove them and start over.")
  (princ))

;; ── LIGHTINGAI_CLEAR ─────────────────────────────────────────────────────────
;;
;; Removes every AI-placed entity. Original floor plan is never touched.
;;
(defun c:LIGHTINGAI_CLEAR ( / layer)
  (lai:println "Removing all AI-placed entities…")
  (foreach layer LAI:LAYERS
    (lai:erase-layer-entities layer))
  (lai:println "Done. Original floor plan unchanged.")
  (princ))

;; ── Bridge launcher helper ───────────────────────────────────────────────────
;;
;; Called by the panel when the user clicks Step 3.
;; Writes a shell script + AppleScript, then fires osascript to open
;; a Terminal window and run the Python bridge inside it.
;;
;; Convert a file-path string to a comma-separated list of decimal byte values.
;; AutoCAD LISP writes files in Latin-1; macOS paths are UTF-8.  Writing the
;; raw string into a shell script corrupts non-ASCII chars (e.g. Ö → 0xD6 in
;; the file, but the filesystem expects UTF-8 0xC3 0x96).  Passing the bytes as
;; integers lets Python reconstruct the string with the correct encoding.
(defun lai:path-bytes (s / i result b)
  (setq result "" i 0)
  (while (< i (strlen s))
    (setq b (vl-string-elt s i))
    (setq result (strcat result (if (> i 0) "," "") (itoa b)))
    (setq i (1+ i))
  )
  result
)

(defun lai:run-bridge (dwg-path / fp)
  (setq dwg-path (vl-string-trim " " (if dwg-path dwg-path "")))
  (cond
    ((= dwg-path "")
     (lai:println "No DWG file selected. Click the [...] button first."))
    ((not (findfile dwg-path))
     (lai:println (strcat "File not found: " dwg-path)))
    (T
     ;; 1. Write the DWG path as decimal byte values — pure ASCII, no encoding issues.
     ;;    Python will decode bytes([...]).decode('latin-1') back to the correct path.
     (setq fp (open "/tmp/lai_dwg_bytes.txt" "w"))
     (write-line (lai:path-bytes dwg-path) fp)
     (close fp)

     ;; 2. Write the shell script.  Uses a Python heredoc so no shell-quoting
     ;;    gymnastics are needed around the decoded path.
     (setq fp (open "/tmp/lai_bridge.sh" "w"))
     (write-line "#!/bin/bash" fp)
     (write-line "cd ~/ai-lighting" fp)
     (write-line "python3 - <<'PYEOF'" fp)
     (write-line "import subprocess" fp)
     (write-line "raw = open('/tmp/lai_dwg_bytes.txt').read().strip()" fp)
     (write-line "path = bytes([int(x) for x in raw.split(',')]).decode('latin-1')" fp)
     (write-line "subprocess.run(['python3', 'autocad-plugin/lisp/lightingai_bridge.py', path])" fp)
     (write-line "PYEOF" fp)
     (write-line "" fp)
     (write-line "echo ''" fp)
     (write-line "echo '[LightingAI] Done. Return to AutoCAD and click Step 4: Place Lights.'" fp)
     (close fp)

     ;; 3. Launch LightingAI_Bridge.app — a shell .app bundle that opens Terminal
     ;;    and runs /tmp/lai_bridge.sh.  No Python version dependency.
     (startapp (strcat (getenv "HOME") "/LightingAI_Bridge.app") "")
     (lai:println (strcat "Bridge launched for: " (vl-filename-base dwg-path) ".dwg"))
     (lai:println "Watch Terminal. When it says Done, click Step 4: Place Lights.")))
  (princ))


;; ── LIGHTINGAI  (launches the Python GUI panel) ───────────────────────────────
;;
;; Opens lai_gui.py — a native macOS window with four large step buttons.
;; Each button sends the corresponding command back to AutoCAD via AppleScript.
;; macOS will ask for Accessibility permission the first time you click a button:
;;   System Settings → Privacy & Security → Accessibility → enable Terminal.
;;
;; Short alias:  LAI
;;
(defun c:LIGHTINGAI ( / home app)
  (setq home (getenv "HOME"))
  (setq app  (strcat home "/LightingAI.app"))

  ;; ~/LightingAI.app is a real macOS .app bundle created during setup.
  ;; startapp on AutoCAD for Mac requires a proper .app bundle — raw binaries
  ;; like /bin/bash or /usr/bin/osascript silently fail.
  (if (findfile app)
    (startapp app "")
    (progn
      (lai:println "ERROR: ~/LightingAI.app not found.")
      (lai:println "Run this in Terminal to fix:")
      (lai:println (strcat "  python3 " home "/ai-lighting/autocad-plugin/lisp/lai_setup.py"))))

  (lai:println "LightingAI panel opening — check top-right of your screen.")
  (lai:println "(If nothing appears after 5 s, check: /tmp/lai_gui.log)")
  (princ))

(defun c:LAI () (c:LIGHTINGAI))


;; ── LIGHTINGAI_BRIDGE_STEP ────────────────────────────────────────────────────
;;
;; Called by the GUI when the user clicks Step 3.
;; Reads the DWG path recorded by LIGHTINGAI_GRID in Step 1.
;; No file picker — the system already knows which floor plan is active.
;;
(defun c:LIGHTINGAI_BRIDGE_STEP ( / origin-fp line json-str bytes-start bytes-end bytes-str dwg-path)
  (if (not (lai:file-exists LAI:ORIGIN-FILE))
    (progn
      (lai:println "╔══════════════════════════════════════════════════════════╗")
      (lai:println "║  STOP — Step 1 not completed!                            ║")
      (lai:println "║  Run LIGHTINGAI_GRID first to detect the floor plan.     ║")
      (lai:println "╚══════════════════════════════════════════════════════════╝")
      (exit)))

  ;; Read the dwg_bytes array from origin.json and reconstruct the path.
  ;; The bytes were written by lai:write-origin-file as Latin-1 decimal ints.
  (setq origin-fp (open LAI:ORIGIN-FILE "r"))
  (setq json-str (read-line origin-fp))
  (close origin-fp)

  ;; Extract the array: find "[" after "dwg_bytes" and "]" after it
  (setq bytes-start (vl-string-search "[" json-str
                       (vl-string-search "dwg_bytes" json-str 0)))
  (setq bytes-end   (vl-string-search "]" json-str bytes-start))

  (if (or (null bytes-start) (null bytes-end))
    (progn
      ;; origin.json written by old code without dwg_bytes — fall back to file picker
      (lai:println "Grid file predates this update. Run LIGHTINGAI_GRID again to refresh.")
      (exit)))

  (setq bytes-str (substr json-str (+ bytes-start 2) (- bytes-end bytes-start 1)))

  ;; Write byte list to a temp file; the shell script's Python will decode it
  (setq origin-fp (open "/tmp/lai_dwg_bytes.txt" "w"))
  (write-line bytes-str origin-fp)
  (close origin-fp)

  ;; Verify the decoded path will be valid before launching Terminal
  (lai:run-bridge-from-bytes)
  (princ))

;; Launch the bridge using the byte-encoded DWG path in /tmp/lai_dwg_bytes.txt
(defun lai:run-bridge-from-bytes ( / fp)
  (setq fp (open "/tmp/lai_bridge.sh" "w"))
  (write-line "#!/bin/bash" fp)
  (write-line "cd ~/ai-lighting" fp)
  (write-line "PYBIN=$(command -v python3.13 || command -v python3.12 || command -v python3)" fp)
  (write-line "\"$PYBIN\" - <<'PYEOF'" fp)
  (write-line "import subprocess, os, sys" fp)
  (write-line "raw = open('/tmp/lai_dwg_bytes.txt').read().strip()" fp)
  (write-line "path = bytes([int(x) for x in raw.split(',')]).decode('latin-1')" fp)
  (write-line "if not os.path.exists(path):" fp)
  (write-line "    print(f'[LightingAI] ERROR: File not found: {path}')" fp)
  (write-line "    raise SystemExit(1)" fp)
  (write-line "print(f'[LightingAI] Processing: {os.path.basename(path)}')" fp)
  (write-line "result = subprocess.run([sys.executable, 'autocad-plugin/lisp/lightingai_bridge.py', path])" fp)
  (write-line "PYEOF" fp)
  (write-line "" fp)
  (write-line "echo ''" fp)
  (write-line "echo '[LightingAI] Done. Return to AutoCAD and click Step 4: Place Lights.'" fp)
  (close fp)

  ;; Launch LightingAI_Bridge.app — a shell .app bundle created by lai_setup.py
  ;; that opens a Terminal window and runs /tmp/lai_bridge.sh.
  (startapp (strcat (getenv "HOME") "/LightingAI_Bridge.app") "")
  (lai:println "Bridge launched for the current floor plan.")
  (lai:println "Watch Terminal. When it says Done, click Step 4: Place Lights.")
  (princ))


;; ── LIGHTINGAI_CONFIG ────────────────────────────────────────────────────────
;;
;; Interactive configurator: lets the user pick the number of light types and
;; choose a symbol shape + color for each type before running the Python bridge.
;; Writes /tmp/lightingai_typeconfig.json which the bridge reads automatically.
;;
(defun c:LIGHTINGAI_CONFIG ( / n i t-letter
                               shape-names color-names
                               default-shapes default-colors
                               shape-idx color-idx shape color
                               json-str fp)

  ;; Default symbol shape per position  A=Circle  B=Square  C=Diamond  D=Triangle  E=Cross  F=Circle
  (setq default-shapes '(1 2 3 4 5 1))
  ;; Default color per position  A=Magenta(6)  B=Red(1)  C=Cyan(4)  D=Yellow(2)  E=Blue(5)  F=Green(3)
  (setq default-colors '(6 1 4 2 5 3))
  (setq shape-names '("Circle" "Square" "Diamond" "Triangle" "Cross"))
  (setq color-names '("Red" "Yellow" "Green" "Cyan" "Blue" "Magenta" "Orange"))

  (lai:println "=== LightingAI — Step 2: Light Type Configurator ===")
  (lai:println "REQUIRED: Choose a symbol and color for each light type.")
  (lai:println "Press Enter at any prompt to accept the default shown in < >.")

  ;; ── Number of types ──────────────────────────────────────────────────────
  (initget 6)   ; bit 2 = no zero, bit 4 = no negative; null (Enter) still allowed
  (setq n (getint "\n[LightingAI] How many light types do you want? (1-6) <5>: "))
  (if (null n) (setq n 5))
  (if (> n 6)  (setq n 6))
  (if (< n 1)  (setq n 1))

  ;; ── Per-type prompts ─────────────────────────────────────────────────────
  (setq json-str "[")
  (setq i 0)
  (while (< i n)
    (setq t-letter (nth i '("A" "B" "C" "D" "E" "F")))

    ;; Shape
    (lai:println (strcat "\n  --- Type " t-letter " ---"))
    (lai:println "  Shapes:  1=Circle  2=Square  3=Diamond  4=Triangle  5=Cross")
    (setq def-si (nth i default-shapes))
    (initget 6)
    (setq shape-idx (getint
      (strcat "  Shape for Type " t-letter " (1-5) <" (itoa def-si) ">: ")))
    (if (null shape-idx) (setq shape-idx def-si))
    (if (< shape-idx 1) (setq shape-idx 1))
    (if (> shape-idx 5) (setq shape-idx 5))
    (setq shape (nth (1- shape-idx) shape-names))

    ;; Color
    (lai:println "  Colors:  1=Red  2=Yellow  3=Green  4=Cyan  5=Blue  6=Magenta  7=Orange")
    (setq def-ci (nth i default-colors))
    (initget 6)
    (setq color-idx (getint
      (strcat "  Color for Type " t-letter " (1-7) <" (itoa def-ci) ">: ")))
    (if (null color-idx) (setq color-idx def-ci))
    (if (< color-idx 1) (setq color-idx 1))
    (if (> color-idx 7) (setq color-idx 7))
    (setq color (nth (1- color-idx) color-names))

    (lai:println (strcat "  → Type " t-letter ": " shape " / " color))

    ;; Append JSON entry
    (if (> i 0) (setq json-str (strcat json-str ",")))
    (setq json-str (strcat json-str
      "{\"type\":\"" t-letter "\","
      "\"shape\":\"" shape "\","
      "\"color\":\"" color "\"}"))

    (setq i (1+ i))
  )
  (setq json-str (strcat json-str "]"))

  ;; Write to file
  (setq fp (open LAI:TYPECONFIG-FILE "w"))
  (write-line json-str fp)
  (close fp)

  (lai:println (strcat "\nConfiguration saved for " (itoa n) " light type(s)."))
  (lai:println (strcat "Config file: " LAI:TYPECONFIG-FILE))
  (lai:println "Next: run the Python bridge in Terminal, then LIGHTINGAI_PLACE.")
  (princ))


;; ── LIGHTINGAI_STATUS ────────────────────────────────────────────────────────
;;
;; Shows what is currently configured.
;;
(defun c:LIGHTINGAI_STATUS ( / fp line)
  (lai:println "=== LightingAI Status ===")
  (if (lai:file-exists LAI:ORIGIN-FILE)
    (progn
      (setq fp (open LAI:ORIGIN-FILE "r"))
      (setq line (read-line fp))
      (close fp)
      (lai:println (strcat "Origin file : " LAI:ORIGIN-FILE))
      (lai:println (strcat "Origin data : " line)))
    (lai:println "Origin file : not yet written (run LIGHTINGAI_GRID first)"))
  (if (lai:file-exists LAI:COMMANDS-FILE)
    (lai:println (strcat "Commands    : READY — " LAI:COMMANDS-FILE))
    (lai:println "Commands    : NOT READY — run Python bridge first"))
  (if (lai:file-exists LAI:TYPECONFIG-FILE)
    (lai:println (strcat "Type config : READY — " LAI:TYPECONFIG-FILE))
    (lai:println "Type config : using defaults (run LIGHTINGAI_CONFIG to customise)"))
  (lai:println "=========================")
  (princ))

;; ── Load confirmation ─────────────────────────────────────────────────────────
(lai:println "╔════════════════════════════════════════════════╗")
(lai:println "║   LIGHTING AI — MIKA80-E Rossmann (Mac)        ║")
(lai:println "╠════════════════════════════════════════════════╣")
(lai:println "║  Type  LIGHTINGAI  (or  LAI)  to open          ║")
(lai:println "║  the graphical 4-step control panel.           ║")
(lai:println "╠════════════════════════════════════════════════╣")
(lai:println "║  Individual commands (advanced):               ║")
(lai:println "║  LIGHTINGAI_GRID    LIGHTINGAI_CONFIG          ║")
(lai:println "║  LIGHTINGAI_PLACE   LIGHTINGAI_CLEAR           ║")
(lai:println "║  LIGHTINGAI_STATUS  LIGHTINGAI_SETUP           ║")
(lai:println "╚════════════════════════════════════════════════╝")
(lai:println "Rossmann standard: 625mm tile pitch, Startmaß 1.00m/2.00m (luminaires every 2 tiles = 1250mm)")
(princ)
